FME workspace main.fmw

Parameters:
- PROJECT_NAME = MyProject
- STATE = start   # State
- STAGE = init   # Stage
- PARENT_JOB =   # Parent Job Id
- FME_JOB_ID = 0   # FME Flow Job ID
- FME_SHAREDRESOURCE_DATA = $(FME_MF_DIR_USERTYPED)FME_SHAREDRESOURCE_DATA   # FME Flow Data Directory

Note: with t as ( / select 1 lev, cast(job_id as nvarchar(max)) path , job_id, context_id / from fme_job_history_debug_2308 / where job_id = 7487663 / union all / select t.lev + 1, t.path + '/' + cast(c.job_id as nvarchar(max)) path, c.job_id, c.context_id / from t, fme_job_history_debug_2308 c / where t.context_id = c.tag / ) / select * / from t, fme_job_history_debug_2308 j / where t.job_id = j.job_id / order by j.date_started
Note: 413ae0ab6e3a7322ad1b0c95e11f1c66c254daac
Note: abandoned idea: / 1. create job queue / 2. add jobs to queue / 3. take note - what jobs did we post / 4. start queue by assigning engine(s) to it
Creator
    GEOMTYPE = Geometry Object
    NUM = 1
    CREATED -> FilenamePartExtractor
FilenamePartExtractor
    DIRNAME_ATTR = repository_name
    SRC_ATTR = $(FME_MF_DIR_USERTYPED)
    -> AttributeFilter_stage
AttributeFilter_stage
    ATTR_NAME = stage
    ATTR_VALUES = init,progress,<Empty>,<Missing>,<Null>,<Unfiltered>
    init -> AttributeFilter
    progress -> HTTPCaller_Queued
    <EMPTY> -> Terminator
    <MISSING> -> Terminator
    <NULL> -> Terminator
    <UNFILTERED> -> Terminator
Note: http://localhost/fmeapiv4/jobs?engineName=&limit=100&offset=0&repository=&sort=timeFinished_desc&sourceID=&sourceType=&status=cancelled%2C%20failure%2C%20success&userID=&workspace=&cb=1747494259377 / http://localhost/fmeapiv4/jobs?engineName=&limit=100&offset=0&repository=&sort=&sourceID=&sourceType=&status=queued&userID=&workspace=&cb=1747494334076 / http://localhost/fmeapiv4/jobs?engineName=&limit=100&offset=0&repository=&sort=&sourceID=&sourceType=&status=running&userID=&workspace=&cb=1747494368848
AttributeFilter
    ATTR_NAME = state
    ATTR_VALUES = start,<Unfiltered>,<Empty>,<Missing>,<Null>
    start -> UniqueIdentifierGenerator
    <UNFILTERED> -> AttributeCreator_2
Terminator
    MESSAGE = Translation Terminated
Decelerator
    DECEL_LOOKUP = PERFEATDELAY
    DELAY = 5
    DECEL_TYPE = Per Feature Delay
    -> JSONTemplater_3 [ROOT]
Note: Repost progress check
JSONTemplater_3
    RESULT_ATTRIBUTE = request_body
    ROOT_QUERY_EXPR:
      {
        "publishedParameters": [
          {
            "name": "PARENT_JOB",
            "value": "$(PARENT_JOB)"
          },
          {
            "name": "STAGE",
            "value": "progress"
          },
          {
            "name": "STATE",
            "value": fme:get-attribute("state")
          }
        ]
      }
    VISIBLE_QUERY_VALIDATE = Yes
    -> HTTPCaller_2
Note: lev path job_id context_id job_id repository_name workspace_name job_status date_queued date_started date_finished engine_instance engine_host client_result_host client_result_port result_mode context_id tag / 1 7487663 7487663 context-id-0e939663-0397-450a-beec-b78f9b9166a4 7487663 fgases_automation __FGASES_MAIN__.fmw ABORTED 2025-03-27 00:05:00.0320000 2025-03-27 00:05:00.0360000 2025-03-27 08:20:20.5760000 PANDA-ENG5-B_Engine2 PANDA-ENG5-B 10.50.1.220 -1 0 context-id-0e939663-0397-450a-beec-b78f9b9166a4 Slow / 2 7487663/7487665 7487665 context-id-fe680872-95ad-4af9-976a-2c5f7475516b 7487665 fgases_automation A_Write_FDB_from_Access_to_SQL.fmw SUCCESS 2025-03-27 00:05:03.3130000 2025-03-27 00:05:03.7530000 2025-03-27 00:56:45.7550000 PANDA-ENG5-B_Engine2@7487663 PANDA-ENG5-B 10.50.1.218 61699 0 context-id-fe680872-95ad-4af9-976a-2c5f7475516b context-id-0e939663-0397-450a-beec-b78f9b9166a4 / 2 7487663/7487781 7487781 context-id-7f0e0638-e147-4fb6-83dd-72bdd86b99b9 7487781 fgases_automation 0. Master_dataflow_Import.fmw SUCCESS 2025-03-27 01:00:35.1300000 2025-03-27 01:00:35.1320000 2025-03-27 01:06:15.2850000 PANDA-ENG5-B_Engine2@7487663 PANDA-ENG5-B 10.50.1.218 62384 0 context-id-7f0e0638-e147-4fb6-83dd-72bdd86b99b9 context-id-0e939663-0397-450a-beec-b78f9b9166a4 / 3 7487663/7487781/7487783 7487783 context-id-f4243c7e-4883-4949-9de1-0388de63a284 7487783 fgases_automation 1.SyncReportNetOblig.fmw SUCCESS 2025-03-27 01:00:35.9490000 2025-03-27 01:00:36.3990000 2025-03-27 01:03:03.3630000 PANDA-ENG5-B_Engine2@7487663@7487781 PANDA-ENG5-B 10.50.1.218 62386 0 context-id-f4243c7e-4883-4949-9de1-0388de63a284 context-id-7f0e0638-e147-4fb6-83dd-72bdd86b99b9 / 3 7487663/7487781/7487793 7487793 context-id-4cc33fbd-8ded-4087-b99b-202026015a6f 7487793 fgases_automation 3.BDRRegistry_to_SQL.fmw SUCCESS 2025-03-27 01:03:03.8550000 2025-03-27 01:03:24.3820000 2025-03-27 01:04:42.3900000 PANDA-ENG5-B_Engine2@7487663@7487781 PANDA-ENG5-B 10.50.1.218 62410 0 context-id-4cc33fbd-8ded-4087-b99b-202026015a6f context-id-7f0e0638-e147-4fb6-83dd-72bdd86b99b9 / 2 7487663/7489318 7489318 context-id-10c0fcb2-712c-49aa-b2c4-763d9da3f4e0 7489318 fgases_automation 5.0 Framework - AggregationTool.fmw SUCCESS 2025-03-27 01:18:10.2800000 2025-03-27 01:18:10.2860000 2025-03-27 05:06:13.6480000 PANDA-ENG5-B_Engine2@7487663 PANDA-ENG5-B 10.50.1.218 62917 0 context-id-10c0fcb2-712c-49aa-b2c4-763d9da3f4e0 context-id-0e939663-0397-450a-beec-b78f9b9166a4 / 3 7487663/7489318/7489319 7489319 context-id-0ed7e048-376e-46bc-857b-13155721e6fe 7489319 fgases_automation 5.1 AggregationTool - SQL2FDB.fmw SUCCESS 2025-03-27 01:18:12.8380000 2025-03-27 01:18:13.3070000 2025-03-27 02:18:09.6470000 PANDA-ENG5-B_Engine2@7487663@7489318 PANDA-ENG5-B 10.50.1.218 62919 0 context-id-0ed7e048-376e-46bc-857b-13155721e6fe context-id-10c0fcb2-712c-49aa-b2c4-763d9da3f4e0 / 3 7487663/7489318/7490739 7490739 context-id-47a8ec2f-a893-4da2-9215-28028632ebfa 7490739 fgases_automation 5.3 SQL2FDB_drafts.fmw SUCCESS 2025-03-27 03:11:12.7220000 2025-03-27 03:11:12.7260000 2025-03-27 03:13:32.1870000 PANDA-ENG5-B_Engine2@7487663@7489318 PANDA-ENG5-B 10.50.1.218 64518 0 context-id-47a8ec2f-a893-4da2-9215-28028632ebfa context-id-10c0fcb2-712c-49aa-b2c4-763d9da3f4e0 / 3 7487663/7489318/7490743 7490743 context-id-85d5f967-52b9-43fb-9d10-b6f1034162e3 7490743 fgases_automation 5.4 SQL2FDB_rejected.fmw SUCCESS 2025-03-27 03:13:40.5600000 2025-03-27 03:13:53.1970000 2025-03-27 03:21:48.2790000 PANDA-ENG5-B_Engine2@7487663@7489318 PANDA-ENG5-B 10.50.1.218 64532 0 context-id-85d5f967-52b9-43fb-9d10-b6f1034162e3 context-id-10c0fcb2-712c-49aa-b2c4-763d9da3f4e0 / 3 7487663/7489318/7490842 7490842 context-id-1139e8ae-4b30-43b5-9525-2137c6a3d1f5 7490842 fgases_automation 5.232 TransactionsMap.fmw SUCCESS 2025-03-27 04:11:36.8540000 2025-03-27 04:11:36.8600000 2025-03-27 04:11:39.7310000 PANDA-ENG5-B_Engine2@7487663@7489318 PANDA-ENG5-B 10.50.1.218 65050 0 context-id-1139e8ae-4b30-43b5-9525-2137c6a3d1f5 context-id-10c0fcb2-712c-49aa-b2c4-763d9da3f4e0
HTTPCaller_Completed
    ADDITIONAL_URL_PARAMETERS = limit;-1 offset;-1 repository;@Value(repository_name) workspace;@Value(state).fmw
    CLIENT_CERTIFICATE_TYPE = NONE
    CONNECTION_TIMEOUT_LENGTH = 60
    CUSTOM_HEADERS = Authorization;fmetoken token=413ae0ab6e3a7322ad1b0c95e11f1c66c254daac
    ERROR_ATTR = _error
    FOLLOW_REDIRECTS = FOLLOW_WITH_GET
    HTTP_METHOD = GET
    MAX_HTTP_VERSION = HTTP_2
    MAX_TRANSFERS_IN_PROGRESS = 1
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = response_body
    TARGET_ATTR_ENCODING = auto-detect
    TARGET_URL = http://localhost/fmerest/v3/transformations/jobs/completed
    TRANSFER_TIMEOUT_LENGTH = 90
    USE_COOKIES = No
    VERIFY_SSL_CERTIFICATES = Yes
    -> JSONExtractor_3
JSONExtractor_3
    EXTRACT_QUERY_TABLE = totalCount json["totalCount"]
    JSON_DOCUMENT = @Value(response_body)
    READ_FROM_FILE = NO
    EVALUATED -> JSONFragmenter_2
JSONFragmenter_2
    EXPLODE_FORMAT = JSON
    EXTRACT_ATTR = Yes
    JSON_ATTR = response_body
    JSON_QUERY = json["items"][*]
    NEW_ATTRIBUTES = job.status buffer
    PREF_STRING = job.
    READ_FROM_FILE = NO
    RECURSIVE = NO
    REJECT_EMPTY_LISTS = YES
    FRAGMENTS -> AttributeFilter_2
AttributeFilter_2
    ATTR_NAME = job.status
    ATTR_VALUES = SUCCESS,<Empty>,<Missing>,<Null>,<Unfiltered>
    SUCCESS -> Aggregator_2
Aggregator_2
    ACCUM_ATTRS_NAME = Drop Incoming Attributes
    COUNT_ATTR = successfulCount
    GROUP_BY = project_dir repository_name stage state totalCount
    MODE = Attributes Only
    SEP = ,
    AGGREGATE -> Tester_3
Tester_3
    BOOL_OP = OR
    TEST_CLAUSE = TEST @Value(totalCount) = @Value(successfulCount)
    TEST_MODE = TEST
    PASSED -> Tester_3_Passed
    PASSED -> AttributeCreator_2
    FAILED -> Terminator_2
AttributeCreator_2
    ATTR_TABLE = SET_TO batch_dir (varchar(200)) = $(FME_SHAREDRESOURCE_DATA)/$(PROJECT_NAME)/@Value(repository_name)
    -> AttributeValueMapper
AttributeValueMapper
    DEFAULT_VALUE = __not_found__
    LUT = start,download_unzip,download_unzip,validate_transform,validate_transform,load,load,cleanup
    MAPPING_DIRECTION = FORWARD
    SRC = state
    VAL_ATTR = next_state
    -> AttributeFilter_next_state
Note: { / "NMDirectives": { / "directives": [ / { / "name": "string", / "value": "string" / } / ], / "failureTopics": [ / "string" / ], / "successTopics": [ / "string" / ] / }, / "TMDirectives": { / "rtc": true, / "ttc": 0, / "ttl": 0, / "description": "string", / "priority": 0, / "tag": "string" / }, / "publishedParameters": [ / { / "name": "string" / } / ], / "workspacePath": "string" / }
AttributeFilter_next_state
    ATTR_NAME = next_state
    ATTR_VALUES = download_unzip,validate_transform,load,cleanup,<Empty>,<Missing>,<Null>,<Unfiltered>
    download_unzip -> JSONTemplater [ROOT]
    validate_transform -> FeatureReader [INITIATOR]
    load -> Terminator_3
    cleanup -> Terminator_3
    <EMPTY> -> Terminator_4
    <MISSING> -> Terminator_4
    <NULL> -> Terminator_4
    <UNFILTERED> -> Terminator_4
JSONTemplater
    RESULT_ATTRIBUTE = request_body
    ROOT_QUERY_EXPR:
      {
        "publishedParameters": [
          {
            "name": "OUTPUT_FOLDER",
            "value": fme:get-attribute("batch_dir")
          }
        ]
      }
    VISIBLE_QUERY_VALIDATE = Yes
    -> HTTPCaller
FeatureReader
    ATTRIBUTES = PATH,"path_unix,path_windows,path_rootname,path_filename,path_extension,path_directory_unix,path_directory_windows,path_type,fme_geometry{0}"
    ATTR_ACCUM_MODE = Merge Initiator and Result
    ATTR_CONFLICT_RES = Use Result
    ATTR_IGNORE_NULLS = No
    COMBINE_GEOM = Use Result
    DATASET = @Value(batch_dir)
    FORMAT = PATH
    INITIATOR_FIRST_OUTPUT = default
    ORDER_RESULTS = No
    OUTPUT_FEATURES_DISPLAY = Data Features
    PATH_GLOB_PATTERN = *
    PATH_HIDDEN_FILES = INCLUDE
    PATH_NO_EMPTY_PROPERTIES = YES
    PATH_OFFSET_DATETIME = yes
    PATH_RECURSE_DIRECTORIES = NO
    PATH_RETRIEVE_FILE_PROPERTIES = NO
    PATH_TYPE = DIRECTORY
    PATH_USE_NON_STRING_ATTR = yes
    PATH -> JSONTemplater_4 [ROOT]
JSONTemplater_4
    RESULT_ATTRIBUTE = request_body
    ROOT_QUERY_EXPR:
      {
        "publishedParameters": [
          {
            "name": "DATA_FOLDER",
            "value": fme:get-attribute("path_unix")
          }
        ]
      }
    VISIBLE_QUERY_VALIDATE = Yes
    -> HTTPCaller
HTTPCaller
    CLIENT_CERTIFICATE_TYPE = NONE
    CONNECTION_TIMEOUT_LENGTH = 60
    CONTENT_TYPE_LOOKUP = application/json
    CUSTOM_HEADERS = Authorization;fmetoken token=413ae0ab6e3a7322ad1b0c95e11f1c66c254daac
    ERROR_ATTR = _error
    FOLLOW_REDIRECTS = FOLLOW_WITH_GET
    HTTP_METHOD = POST
    MAX_HTTP_VERSION = HTTP_2
    MAX_TRANSFERS_IN_PROGRESS = 1
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = response_body
    TARGET_ATTR_ENCODING = auto-detect
    TARGET_URL = http://localhost/fmerest/v3/transformations/submit/@Value(repository_name)/@Value(next_state).fmw
    TRANSFER_TIMEOUT_LENGTH = 90
    UPLOAD_BODY = @Value(request_body)
    UPLOAD_TYPE = STRING_UPLOAD
    USE_COOKIES = No
    VERIFY_SSL_CERTIFICATES = Yes
    UPLOAD_CONTENT_TYPE = JSON (application/json)
    -> Aggregator_3
Aggregator_3
    ACCUM_ATTRS_NAME = Drop Incoming Attributes
    GROUP_BY = next_state repository_name
    MODE = Attributes Only
    SEP = ,
    AGGREGATE -> JSONTemplater_2 [ROOT]
JSONTemplater_2
    RESULT_ATTRIBUTE = request_body
    ROOT_QUERY_EXPR:
      {
        "publishedParameters": [
          {
            "name": "PARENT_JOB",
            "value": "$(FME_JOB_ID)"
          },
          {
            "name": "STAGE",
            "value": "progress"
          },
          {
            "name": "STATE",
            "value": fme:get-attribute("next_state")
          }
        ]
      }
    VISIBLE_QUERY_VALIDATE = Yes
    -> HTTPCaller_2
HTTPCaller_2
    CLIENT_CERTIFICATE_TYPE = NONE
    CONNECTION_TIMEOUT_LENGTH = 60
    CONTENT_TYPE_LOOKUP = application/json
    CUSTOM_HEADERS = Authorization;fmetoken token=413ae0ab6e3a7322ad1b0c95e11f1c66c254daac
    ERROR_ATTR = _error
    FOLLOW_REDIRECTS = FOLLOW_WITH_GET
    HTTP_METHOD = POST
    MAX_HTTP_VERSION = HTTP_2
    MAX_TRANSFERS_IN_PROGRESS = 1
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = response_body
    TARGET_ATTR_ENCODING = auto-detect
    TARGET_URL = http://localhost/fmerest/v3/transformations/submit/@Value(repository_name)/main.fmw
    TRANSFER_TIMEOUT_LENGTH = 90
    UPLOAD_BODY = @Value(request_body)
    UPLOAD_TYPE = STRING_UPLOAD
    USE_COOKIES = No
    VERIFY_SSL_CERTIFICATES = Yes
    UPLOAD_CONTENT_TYPE = JSON (application/json)
Terminator_3
    MESSAGE = Not Impelmented
Terminator_4
    MESSAGE = Unexpected state
Note: move on
Tester_3_Passed: Logger
    LOG_FEATURE = LOG_ONLY
    MAXCOORDS = 20
    MAXFEATS = 20
    MESSAGE = Feature is:
    SEVERITY = INFO
Terminator_2
    MESSAGE = Translation Terminated

Bookmark: Copy Repository
Note: since we can't provide anything when submitting jobs that can later be used for filtering when checking status we create a copy of the whole repository for each batch
Note: create new repository for this batch
UniqueIdentifierGenerator
    UUID_ATTR = _ulid
    UUID_FORMAT = ULID
    -> AttributeCreator
AttributeCreator
    ATTR_TABLE:
      SET_TO original_repository_name (varchar(200)) = @Value(repository_name)
      SET_TO repository_name (buffer) = $(PROJECT_NAME)-$(FME_JOB_ID)-@Value(_ulid)
    -> HTTPCaller_5
HTTPCaller_5
    CLIENT_CERTIFICATE_TYPE = NONE
    CONNECTION_TIMEOUT_LENGTH = 60
    CONTENT_TYPE_LOOKUP = application/x-www-form-urlencoded
    CUSTOM_HEADERS = Authorization;fmetoken token=413ae0ab6e3a7322ad1b0c95e11f1c66c254daac
    ERROR_ATTR = _error
    FOLLOW_REDIRECTS = FOLLOW_WITH_GET
    HTTP_METHOD = POST
    MAX_HTTP_VERSION = HTTP_2
    MAX_TRANSFERS_IN_PROGRESS = 1
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = response_body
    TARGET_ATTR_ENCODING = auto-detect
    TARGET_URL = http://localhost/fmerest/v3/repositories
    TRANSFER_TIMEOUT_LENGTH = 90
    UPLOAD_BODY = description=Temporary repository for batch job&name=@Value(repository_name)
    UPLOAD_TYPE = STRING_UPLOAD
    USE_COOKIES = No
    VERIFY_SSL_CERTIFICATES = Yes
    UPLOAD_CONTENT_TYPE = URL Encoded (application/x-www-form-urlencoded)
    -> TempPathnameCreator
Note: download items
TempPathnameCreator
    PATHNAME_ATTR = _pathname
    -> HTTPCaller_4
HTTPCaller_4
    ADDITIONAL_URL_PARAMETERS = type;WORKSPACE
    CLIENT_CERTIFICATE_TYPE = NONE
    CONNECTION_TIMEOUT_LENGTH = 60
    CUSTOM_HEADERS = Authorization;fmetoken token=413ae0ab6e3a7322ad1b0c95e11f1c66c254daac
    ERROR_ATTR = _error
    FOLLOW_REDIRECTS = FOLLOW_WITH_GET
    HTTP_METHOD = GET
    MAX_HTTP_VERSION = HTTP_2
    MAX_TRANSFERS_IN_PROGRESS = 1
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = response_body
    TARGET_ATTR_ENCODING = auto-detect
    TARGET_URL = http://localhost/fmerest/v3/repositories/@Value(original_repository_name)/items
    TRANSFER_TIMEOUT_LENGTH = 90
    USE_COOKIES = No
    VERIFY_SSL_CERTIFICATES = Yes
    -> JSONFragmenter
JSONFragmenter
    EXPLODE_FORMAT = JSON
    EXTRACT_ATTR = Yes
    JSON_ATTR = response_body
    JSON_QUERY = json["items"][*]
    NEW_ATTRIBUTES = workspace.name buffer
    PREF_STRING = workspace.
    READ_FROM_FILE = NO
    RECURSIVE = NO
    REJECT_EMPTY_LISTS = YES
    FRAGMENTS -> HTTPCaller_6
HTTPCaller_6
    ADDITIONAL_URL_PARAMETERS = accept;contents
    CLIENT_CERTIFICATE_TYPE = NONE
    CONNECTION_TIMEOUT_LENGTH = 60
    CUSTOM_HEADERS = Authorization;fmetoken token=413ae0ab6e3a7322ad1b0c95e11f1c66c254daac
    ERROR_ATTR = _error
    FILE_PATH_ATTR = workspace.temp_filepath
    FOLLOW_REDIRECTS = FOLLOW_WITH_GET
    HTTP_METHOD = GET
    MAX_HTTP_VERSION = HTTP_2
    MAX_TRANSFERS_IN_PROGRESS = 1
    MINIMUM_ENCRYPTION_LEVEL = OS_DEFAULT
    OUTPUT_FILENAME = @Value(_pathname)/@Value(workspace.name)
    REDIRECT_AUTH = ORIGINAL_DOMAIN_ONLY
    RESPONSE_TYPE = File
    STATUS_CODE_ATTR = _http_status_code
    TARGET_URL = http://localhost/fmerest/v3/repositories/@Value(original_repository_name)/items/@Value(workspace.name)?accept=contents
    TRANSFER_TIMEOUT_LENGTH = 90
    USE_COOKIES = No
    VERIFY_SSL_CERTIFICATES = Yes
    -> HTTPCaller_7
Note: publish copies to batch repository
HTTPCaller_7
    CLIENT_CERTIFICATE_TYPE = NONE
    CONNECTION_TIMEOUT_LENGTH = 60
    CONTENT_TYPE_LOOKUP = application/octet-stream
    CUSTOM_HEADERS = Authorization;fmetoken token=413ae0ab6e3a7322ad1b0c95e11f1c66c254daac Content-Disposition;attachment; filename="@Value(workspace.name)"
    ERROR_ATTR = _error
    FOLLOW_REDIRECTS = FOLLOW_WITH_GET
    HTTP_METHOD = POST
    MAX_HTTP_VERSION = HTTP_2
    MAX_TRANSFERS_IN_PROGRESS = 1
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = response_body
    TARGET_ATTR_ENCODING = auto-detect
    TARGET_URL = http://localhost/fmerest/v3/repositories/@Value(repository_name)/items
    TRANSFER_TIMEOUT_LENGTH = 90
    UPLOAD_FILE = @Value(workspace.temp_filepath)
    UPLOAD_TYPE = FILE_UPLOAD
    USE_COOKIES = No
    VERIFY_SSL_CERTIFICATES = Yes
    UPLOAD_CONTENT_TYPE = Binary (application/octet-stream)
    -> Aggregator
Aggregator
    ACCUM_ATTRS_NAME = Drop Incoming Attributes
    GROUP_BY = stage state repository_name
    MODE = Attributes Only
    SEP = ,
    AGGREGATE -> AttributeCreator_2

Bookmark: Queued or Running
HTTPCaller_Queued
    ADDITIONAL_URL_PARAMETERS = limit;-1 offset;-1 repository;@Value(repository_name) workspace;@Value(state).fmw
    CLIENT_CERTIFICATE_TYPE = NONE
    CONNECTION_TIMEOUT_LENGTH = 60
    CUSTOM_HEADERS = Authorization;fmetoken token=413ae0ab6e3a7322ad1b0c95e11f1c66c254daac
    ERROR_ATTR = _error
    FOLLOW_REDIRECTS = FOLLOW_WITH_GET
    HTTP_METHOD = GET
    MAX_HTTP_VERSION = HTTP_2
    MAX_TRANSFERS_IN_PROGRESS = 1
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = response_body
    TARGET_ATTR_ENCODING = auto-detect
    TARGET_URL = http://localhost/fmerest/v3/transformations/jobs/queued
    TRANSFER_TIMEOUT_LENGTH = 90
    USE_COOKIES = No
    VERIFY_SSL_CERTIFICATES = Yes
    -> JSONExtractor
JSONExtractor
    EXTRACT_QUERY_TABLE = totalCount json["totalCount"]
    JSON_DOCUMENT = @Value(response_body)
    READ_FROM_FILE = NO
    EVALUATED -> Tester
Tester
    BOOL_OP = OR
    TEST_CLAUSE = TEST @Value(totalCount) > 0
    TEST_MODE = TEST
    PASSED -> Decelerator
    FAILED -> HTTPCaller_Running
HTTPCaller_Running
    ADDITIONAL_URL_PARAMETERS = limit;-1 offset;-1 repository;@Value(repository_name) workspace;@Value(state).fmw
    CLIENT_CERTIFICATE_TYPE = NONE
    CONNECTION_TIMEOUT_LENGTH = 60
    CUSTOM_HEADERS = Authorization;fmetoken token=413ae0ab6e3a7322ad1b0c95e11f1c66c254daac
    ERROR_ATTR = _error
    FOLLOW_REDIRECTS = FOLLOW_WITH_GET
    HTTP_METHOD = GET
    MAX_HTTP_VERSION = HTTP_2
    MAX_TRANSFERS_IN_PROGRESS = 1
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = response_body
    TARGET_ATTR_ENCODING = auto-detect
    TARGET_URL = http://localhost/fmerest/v3/transformations/jobs/running
    TRANSFER_TIMEOUT_LENGTH = 90
    USE_COOKIES = No
    VERIFY_SSL_CERTIFICATES = Yes
    -> JSONExtractor_2
JSONExtractor_2
    EXTRACT_QUERY_TABLE = totalCount json["totalCount"]
    JSON_DOCUMENT = @Value(response_body)
    READ_FROM_FILE = NO
    EVALUATED -> Tester_2
Tester_2
    BOOL_OP = OR
    TEST_CLAUSE = TEST @Value(totalCount) > 0
    TEST_MODE = TEST
    PASSED -> Decelerator
    FAILED -> HTTPCaller_Completed
